# -*- coding: utf-8 -*-
"""Heat organizer draft: native parametric Part objects, mm, not fit-verified."""
from datetime import datetime, timezone, timedelta
from pathlib import Path
import json
import math
import os
import FreeCAD as App
import Part
import MeshPart

PROJECT_ROOT = Path(os.environ.get('ORGANIZER_PROJECT_ROOT', r'C:\Users\Twibap\Workspace\Organizers'))
MEASUREMENTS = json.loads((PROJECT_ROOT / 'heat-measurements.json').read_text(encoding='utf-8-sig'))


def build_draft():
    doc = App.newDocument('HeatOrganizerDraft')
    doc.Label = 'Heat organizer - DRAFT / base + 2 expansions'
    sheet = doc.addObject('Spreadsheet::Sheet', 'Parameters')
    sheet.Label = 'Draft parameters (mm)'
    sheet.set('A1', 'DRAFT - measured inputs + provisional layout')
    rows = [
        ('BoxX', MEASUREMENTS['box_inside']['length']),
        ('BoxY', MEASUREMENTS['box_inside']['width']),
        ('BoxH', MEASUREMENTS['box_inside']['height']),
        ('Span', 288), ('Wall', 2), ('Base', 2), ('Gap', 0.8),
        ('SleeveW', MEASUREMENTS['sleeved_card']['width']),
        ('SleeveL', MEASUREMENTS['sleeved_card']['height']),
        ('EdgeClear', 1), ('LowerH', 13), ('LidT', 1.6),
        ('LipD', 0.8), ('LipClear', 0.3), ('LipWall', 1.2),
        ('StackReserve', 60), ('Headroom', 2),
        ('SampleStack', MEASUREMENTS['sleeved_card_stack_measurement']['design_basis_stack_height']),
        ('SampleCards', MEASUREMENTS['sleeved_card_stack_measurement']['card_count']),
        ('TotalH', '=BoxH - StackReserve - Headroom'),
        ('PlayerW', '=SleeveW + 2 * EdgeClear + 2 * Wall'),
        ('PlayerL', '=SleeveL + 2 * EdgeClear + 2 * Wall'),
        ('PlayerRegionL', '=2 * PlayerL + Gap'),
        ('CommonL', '=Span - 2 * (PlayerL + Gap)'),
        ('RailW', '=Span - 4 * (PlayerW + Gap)'),
        ('BodyH', '=TotalH - LidT'),
        ('UpperH', '=BodyH - LowerH'),
        ('CardPitch', '=SampleStack / SampleCards'),
    ]
    cells = {}
    for row, (alias, value) in enumerate(rows, 2):
        cell = 'B' + str(row)
        cells[alias] = cell
        sheet.set('A' + str(row), alias)
        sheet.set(cell, str(value) if isinstance(value, str) or alias == 'SampleCards' else str(value) + ' mm')
        sheet.setAlias(cell, alias)
    sheet.setColumnWidth('A', 230)
    sheet.setColumnWidth('B', 250)
    sheet.set('D2', '4 maps + all mats/rules reserved above trays')
    sheet.set('D3', 'Base common mats INCLUDED in measured 4 mm')
    sheet.set('D4', 'Car, gear, scorepad and token sizes unmeasured')
    sheet.set('D5', 'Simple locating lids; retention not validated')
    sheet.setColumnWidth('D', 450)
    doc.recompute()
    p = {alias: float(App.Units.Quantity(sheet.get(cell)).Value) for alias, cell in cells.items()}
    if min(p['RailW'] - 2 * p['Wall'], p['CommonL'] - 2 * p['Wall'], p['UpperH'] - p['Base'] - p['LipD']) <= 0:
        raise ValueError('Parameters leave no usable organizer space')
    construction = doc.addObject('App::DocumentObjectGroup', 'Construction')
    construction.Label = 'Construction - hidden'
    final_group = doc.addObject('App::DocumentObjectGroup', 'OrganizerParts')
    final_group.Label = 'Organizer parts - 36 pieces'
    reference_group = doc.addObject('App::DocumentObjectGroup', 'References')
    reference_group.Label = 'Box / upper stack / sample cards - not printable'
    parts, lids, colors, layout = [], [], {}, []

    def expr(obj, prop, value):
        obj.setExpression(prop, str(value))

    def box(name, width, length, height, x, y, z):
        obj = doc.addObject('Part::Box', name)
        for prop, value in [('Length', width), ('Width', length), ('Height', height),
                            ('Placement.Base.x', x), ('Placement.Base.y', y), ('Placement.Base.z', z)]:
            expr(obj, prop, value)
        construction.addObject(obj)
        return obj

    def feature(name, typ, base, tool):
        obj = doc.addObject(typ, name)
        obj.Base, obj.Tool = base, tool
        obj.Refine = True
        construction.addObject(obj)
        return obj

    def finish(obj, label, color, role, lid=False):
        construction.removeObject(obj)
        final_group.addObject(obj)
        obj.Label = label
        obj.addProperty('App::PropertyString', 'DraftRole', 'Draft').DraftRole = role
        obj.addProperty('App::PropertyString', 'FitStatus', 'Draft').FitStatus = 'Provisional; no physical fit test'
        parts.append(obj)
        colors[obj.Name] = color
        if lid:
            lids.append(obj)
        return obj

    def tray(name, width, length, height, x, y, z, slots, notch, label, color, role):
        outer = box(name + 'Outer', width, length, height, x, y, z)
        cavity_length = '((' + length + ') - ' + str(slots + 1) + ' * Parameters.Wall) / ' + str(slots)
        cavities = []
        for index in range(slots):
            cavity = box(name + 'Pocket' + str(index + 1), '(' + width + ') - 2 * Parameters.Wall',
                         cavity_length, height, '(' + x + ') + Parameters.Wall',
                         '(' + y + ') + Parameters.Wall + ' + str(index) + ' * ((' + cavity_length + ') + Parameters.Wall)',
                         '(' + z + ') + Parameters.Base')
            cavities.append(cavity)
        if slots == 1:
            tool = cavities[0]
        else:
            tool = doc.addObject('Part::MultiFuse', name + 'PocketTool')
            tool.Shapes, tool.Refine = cavities, True
            construction.addObject(tool)
        hollow = feature(name + 'Hollow', 'Part::Cut', outer, tool)
        cutter = doc.addObject('Part::Cylinder', name + 'FingerCut')
        cutter.Placement.Rotation = App.Rotation(App.Vector(0, 0, 1), App.Vector(0, 1, 0))
        cutter.Radius = notch
        expr(cutter, 'Height', 'Parameters.Wall + 2 mm')
        expr(cutter, 'Placement.Base.x', '(' + x + ') + (' + width + ') / 2')
        expr(cutter, 'Placement.Base.y', '(' + y + ') - 1 mm')
        expr(cutter, 'Placement.Base.z', '(' + z + ') + (' + height + ')')
        construction.addObject(cutter)
        final = feature(name, 'Part::Cut', hollow, cutter)
        return finish(final, label, color, role)

    def lid(name, width, length, x, y, label, color, slots=1):
        z = 'Parameters.BodyH'
        plate = box(name + 'Plate', width, length, 'Parameters.LidT', x, y, z)
        lip_w = '(' + width + ') - 2 * (Parameters.Wall + Parameters.LipClear)'
        lip_l = '(' + length + ') - 2 * (Parameters.Wall + Parameters.LipClear)'
        lip_x = '(' + x + ') + Parameters.Wall + Parameters.LipClear'
        lip_y = '(' + y + ') + Parameters.Wall + Parameters.LipClear'
        lip_z = 'Parameters.BodyH - Parameters.LipD'
        outer = box(name + 'LipOuter', lip_w, lip_l, 'Parameters.LipD + 0.05 mm', lip_x, lip_y, lip_z)
        inner = box(name + 'LipInner', '(' + lip_w + ') - 2 * Parameters.LipWall',
                    '(' + lip_l + ') - 2 * Parameters.LipWall', 'Parameters.LipD + 0.1 mm',
                    '(' + lip_x + ') + Parameters.LipWall', '(' + lip_y + ') + Parameters.LipWall', lip_z)
        ring = feature(name + 'Ring', 'Part::Cut', outer, inner)
        # Interrupt the skirt at token tray partitions; otherwise it hits them.
        cavity_length = '((' + length + ') - ' + str(slots + 1) + ' * Parameters.Wall) / ' + str(slots)
        for index in range(slots - 1):
            divider_y = '(' + y + ') + Parameters.Wall + ' + str(index + 1) + ' * (' + cavity_length + ') + ' + str(index) + ' * Parameters.Wall - Parameters.LipClear'
            clearance = box(name + 'DividerGap' + str(index + 1), width, 'Parameters.Wall + 2 * Parameters.LipClear',
                            'Parameters.LipD + 0.1 mm', x, divider_y, lip_z)
            ring = feature(name + 'SkirtClearance' + str(index + 1), 'Part::Cut', ring, clearance)
        obj = feature(name, 'Part::Fuse', plate, ring)
        return finish(obj, label, color, 'lid', True)

    player_colors = [(0.78, 0.22, 0.18), (0.16, 0.43, 0.70), (0.91, 0.66, 0.15), (0.18, 0.58, 0.43),
                     (0.30, 0.33, 0.37), (0.72, 0.70, 0.65), (0.90, 0.40, 0.16), (0.52, 0.32, 0.65)]
    for row in range(2):
        for col in range(4):
            index = row * 4 + col + 1
            name = 'P%02d' % index
            x = '1 mm + %d * (Parameters.PlayerW + Parameters.Gap)' % col
            y = '1 mm + %d * (Parameters.PlayerL + Parameters.Gap)' % row
            color = player_colors[index - 1]
            tray(name + 'Lower', 'Parameters.PlayerW', 'Parameters.PlayerL', 'Parameters.LowerH', x, y, '0 mm',
                 1, 8, name + ' - card tray / sample 24 cards', color, 'player_cards')
            tray(name + 'Upper', 'Parameters.PlayerW', 'Parameters.PlayerL', 'Parameters.UpperH', x, y, 'Parameters.LowerH',
                 1, 8, name + ' - car and gear tray / fit unverified', color, 'player_car_gear')
            lid(name + 'Lid', 'Parameters.PlayerW', 'Parameters.PlayerL', x, y, name + ' - locating lid', color)
            layout.append({'name': name, 'x': 1 + col * (p['PlayerW'] + p['Gap']),
                           'y': 1 + row * (p['PlayerL'] + p['Gap']), 'width': p['PlayerW'],
                           'length': p['PlayerL'], 'height': p['TotalH'], 'role': 'player', 'color': list(color)})
    common_y = '1 mm + 2 * (Parameters.PlayerL + Parameters.Gap)'
    for col in range(4):
        name = 'C%02d' % (col + 1)
        x = '1 mm + %d * (Parameters.PlayerW + Parameters.Gap)' % col
        color = (0.20, 0.45 + col * 0.035, 0.57 + col * 0.035)
        tray(name + 'Body', 'Parameters.PlayerW', 'Parameters.CommonL', 'Parameters.BodyH', x, common_y,
             '0 mm', 1, 12, name + ' - common cards / allocation provisional', color, 'common_cards')
        lid(name + 'Lid', 'Parameters.PlayerW', 'Parameters.CommonL', x, common_y, name + ' - locating lid', color)
        layout.append({'name': name, 'x': 1 + col * (p['PlayerW'] + p['Gap']),
                       'y': 1 + 2 * (p['PlayerL'] + p['Gap']), 'width': p['PlayerW'],
                       'length': p['CommonL'], 'height': p['TotalH'], 'role': 'common', 'color': list(color)})
    rail_x = '1 mm + 4 * (Parameters.PlayerW + Parameters.Gap)'
    for index, (length, y, slots) in enumerate([('Parameters.PlayerRegionL', '1 mm', 3), ('Parameters.CommonL', common_y, 2)], 1):
        name = 'Rail%02d' % index
        color = (0.72, 0.50, 0.22)
        tray(name, 'Parameters.RailW', length, 'Parameters.BodyH', rail_x, y, '0 mm', slots, 6,
             name + ' - generic token compartments / fit unverified', color, 'tokens')
        lid(name + 'Lid', 'Parameters.RailW', length, rail_x, y, name + ' - locating lid', color, slots=slots)
        layout.append({'name': name, 'x': 1 + 4 * (p['PlayerW'] + p['Gap']),
                       'y': 1 if index == 1 else 1 + 2 * (p['PlayerL'] + p['Gap']), 'width': p['RailW'],
                       'length': p['PlayerRegionL'] if index == 1 else p['CommonL'], 'height': p['TotalH'],
                       'role': 'tokens', 'color': list(color), 'slots': slots})
    refs = [box('InternalBoxEnvelope', 'Parameters.BoxX', 'Parameters.BoxY', 'Parameters.BoxH', '0 mm', '0 mm', '0 mm'),
            box('UpperFlatStackReserve', 'Parameters.Span', 'Parameters.Span', 'Parameters.StackReserve', '1 mm', '1 mm', 'Parameters.TotalH'),
            box('SleevedCardSample24', 'Parameters.SleeveW', 'Parameters.SleeveL', 'Parameters.SampleStack',
                '1 mm + Parameters.Wall + Parameters.EdgeClear', '1 mm + Parameters.Wall + Parameters.EdgeClear', 'Parameters.Base')]
    for ref in refs:
        construction.removeObject(ref)
        reference_group.addObject(ref)
        ref.addProperty('App::PropertyString', 'DraftRole', 'Draft').DraftRole = 'reference_not_printable'
    doc.recompute()
    if App.GuiUp:
        import FreeCADGui as Gui
        for obj in construction.Group + refs:
            obj.ViewObject.Visibility = False
        for obj in parts:
            obj.ViewObject.Visibility = obj not in lids
            obj.ViewObject.ShapeColor = colors[obj.Name]
            obj.ViewObject.LineColor = (0.15, 0.17, 0.20)
        Gui.activeDocument().activeView().viewAxonometric()
        Gui.activeDocument().activeView().fitAll()
    return doc, parts, lids, refs, p, cells, layout, colors


def export_draft(doc, parts, lids, refs, p, cells, layout, colors):
    stamp = datetime.now(timezone(timedelta(hours=9))).strftime('%Y%m%d_%H%M%S_%f')
    output = PROJECT_ROOT / 'output' / ('heat_draft_' + stamp)
    output.mkdir(parents=True, exist_ok=False)
    (output / 'stl').mkdir()
    doc.recompute()
    doc.saveAs(str(output / 'HeatOrganizerDraft.FCStd'))
    Part.export(parts, str(output / 'HeatOrganizerDraft-assembled.step'))
    unique = [('P01Lower', 8), ('P01Upper', 8), ('P01Lid', 8), ('C01Body', 4), ('C01Lid', 4),
              ('Rail01', 1), ('Rail01Lid', 1), ('Rail02', 1), ('Rail02Lid', 1)]
    stls = []
    for name, quantity in unique:
        obj = doc.getObject(name)
        shape = obj.Shape.copy()
        # Print lids with the broad top face on the bed and locating ring upward.
        if name.endswith('Lid'):
            shape.rotate(App.Vector(0, 0, 0), App.Vector(1, 0, 0), 180)
        bounds = shape.BoundBox
        shape.translate(App.Vector(-bounds.XMin, -bounds.YMin, -bounds.ZMin))
        mesh = MeshPart.meshFromShape(Shape=shape, LinearDeflection=0.08, AngularDeflection=0.3, Relative=False)
        file_name = name + '_x' + str(quantity) + '.stl'
        mesh.write(str(output / 'stl' / file_name))
        stls.append({'file': 'stl/' + file_name, 'quantity': quantity, 'name': name,
                     'volume_mm3': shape.Volume, 'outer_mm': [shape.BoundBox.XLength, shape.BoundBox.YLength, shape.BoundBox.ZLength],
                     'print_orientation': 'flat lid face down; locating ring up' if name.endswith('Lid') else 'base down'})
    preview = []
    for obj in parts:
        if obj in lids:
            continue
        vertices, triangles = obj.Shape.tessellate(0.25)
        preview.append({'name': obj.Name, 'color': list(colors[obj.Name]),
                        'vertices': [[v.x, v.y, v.z] for v in vertices], 'triangles': [list(t) for t in triangles]})
    (output / 'preview-mesh.json').write_text(json.dumps(preview), encoding='utf-8')
    shared_depth = p['BodyH'] - p['LipD'] - p['Base']
    manifest = {'status': 'draft_not_physical_fit_verified', 'units': 'mm', 'parameters': p, 'cells': cells,
                'layout': layout, 'part_count': len(parts), 'stl_files': stls, 'freecad_version': list(App.Version()),
                'player_card_usable_depth': p['LowerH'] - p['Base'],
                'player_upper_clear_height_under_lip': p['UpperH'] - p['Base'] - p['LipD'],
                'shared_card_usable_depth_under_lip': shared_depth,
                'shared_cards_per_bin_estimate': math.floor((shared_depth - 1) / p['CardPitch']),
                'maximum_print_part_xy': max(max(s['outer_mm'][:2]) for s in stls),
                'assumptions': ['Two track expansions add one player each: 8 player modules.',
                                '24 cards is measured sample, not confirmed final player deck count.',
                                '4-map thickness 50 mm is estimated; complete flat stack must fit 60 mm reserve.',
                                'Car/gear/standee/token and scorepad dimensions unmeasured; all-component fit unverified.',
                                'Scorepads require measured storage allocation; add thickness to upper stack if stored above trays.',
                                'Lids have clearance skirts only; snap fit and vertical transport retention not validated.'],
                'references_not_printable': [obj.Name for obj in refs]}
    (output / 'manifest.json').write_text(json.dumps(manifest, ensure_ascii=False, indent=2), encoding='utf-8')
    (PROJECT_ROOT / 'output' / 'latest-heat-draft.txt').write_text(str(output), encoding='utf-8')
    App.Console.PrintMessage('Heat draft exported to: ' + str(output) + '\n')
    return output


draft_document, draft_parts, draft_lids, draft_refs, draft_parameters, draft_cells, draft_layout, draft_colors = build_draft()
draft_output = export_draft(draft_document, draft_parts, draft_lids, draft_refs, draft_parameters, draft_cells, draft_layout, draft_colors)
