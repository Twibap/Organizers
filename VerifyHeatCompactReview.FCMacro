# -*- coding: utf-8 -*-
from pathlib import Path
import json,math,traceback
import FreeCAD as App
import FreeCADGui as Gui
from PySide import QtCore
root=Path(r'C:\Users\Twibap\Workspace\Organizers')
folder=Path((root/'output/latest-heat-draft.txt').read_text(encoding='utf-8-sig').strip())
def verify():
    report={'passed':False}
    try:
        full=App.openDocument(str(folder/'HeatOrganizerReview.FCStd'))
        visible=[o.Name for o in full.OrganizerParts.Group if o.ViewObject.Visibility]
        assert len(full.OrganizerParts.Group)==30 and len(visible)==16
        assert not full.Construction.ViewObject.Visibility and not full.References.ViewObject.Visibility
        assert len(full.ComponentSamples.Group)==17 and all(o.ViewObject.Visibility for o in full.ComponentSamples.Group)
        view=Gui.activeDocument().activeView();view.fitAll();view.saveImage(str(folder/'HeatOrganizerReview-reopened.png'),1200,900,'White')
        detail=App.openDocument(str(folder/'CarGearTray-Compact.FCStd'))
        assert len(detail.OrganizerParts.Group)==3
        assert all(o.Shape.isValid() and len(o.Shape.Solids)==1 for o in detail.OrganizerParts.Group)
        assert detail.CarGearBody.ViewObject.Visibility and detail.CarScoreTray.ViewObject.Visibility and not detail.CarGearLid.ViewObject.Visibility
        assert len(detail.ComponentSamples.Group)==17 and all(o.ViewObject.Visibility for o in detail.ComponentSamples.Group)
        b=detail.CarGearBody.Shape.BoundBox
        assert math.isclose(b.XLength,110.8,abs_tol=1e-6) and math.isclose(b.YLength,64.8,abs_tol=1e-6)
        assert math.isclose(b.ZMin,11.8,abs_tol=1e-6)
        assert math.isclose(detail.CarGearLid.Shape.BoundBox.ZMax,30.2,abs_tol=1e-6)
        sb=detail.ScoreboardSample.Shape.BoundBox
        assert math.isclose(sb.XLength,100,abs_tol=1e-6) and math.isclose(sb.YLength,60,abs_tol=1e-6) and math.isclose(sb.ZLength,10,abs_tol=1e-6)
        view=Gui.activeDocument().activeView();view.fitAll();view.saveImage(str(folder/'CarGearTray-Compact-reopened.png'),1200,900,'White')
        exploded=App.openDocument(str(folder/'CarGearTray-Compact-Exploded.FCStd'))
        assert math.isclose(exploded.CarGearBody.Shape.BoundBox.ZMin,31.8,abs_tol=1e-6)
        assert math.isclose(exploded.ScoreboardSample.Shape.BoundBox.ZMin,1.2,abs_tol=1e-6)
        view=Gui.activeDocument().activeView();view.fitAll();view.saveImage(str(folder/'CarGearTray-Compact-exploded-reopened.png'),1200,900,'White')
        report.update(passed=True,reopened_without_styling=True,visible_parts=len(visible),component_envelopes=17,
                      compact_reopened=True,compact_valid_parts=3,compact_dimensions_mm=[110.8,64.8,30.2],
                      scoreboard_capacity_mm=[100,60,10],exploded_reopened=True,exploded_display_offset_mm=[0,0,20])
        window=Gui.getMainWindow();window.show();window.raise_();window.activateWindow()
    except Exception:
        report['error']=traceback.format_exc();App.Console.PrintError(report['error'])
    (folder/'review-reopen-status.json').write_text(json.dumps(report,indent=2),encoding='utf-8')
QtCore.QTimer.singleShot(1500,verify)
