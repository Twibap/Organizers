# -*- coding: utf-8 -*-
"""Heat organizer draft: native parametric Part objects, mm, not fit-verified."""
from datetime import datetime, timezone, timedelta
from pathlib import Path
import json
import math
import os
import FreeCAD as App
import Part
import MeshPart

PROJECT_ROOT = Path(os.environ.get('ORGANIZER_PROJECT_ROOT', r'C:\Users\Twibap\Workspace\Organizers'))
MEASUREMENTS = json.loads((PROJECT_ROOT / 'heat-measurements.json').read_text(encoding='utf-8-sig'))


def build_draft():
    doc = App.newDocument('HeatOrganizerDraft')
    doc.Label = 'Heat organizer - DRAFT / base + 2 expansions'
    sheet = doc.addObject('Spreadsheet::Sheet', 'Parameters')
    sheet.Label = 'Draft parameters (mm)'
    sheet.set('A1', 'DRAFT - measured inputs + provisional layout')
    rows = [
        ('BoxX', MEASUREMENTS['box_inside']['length']),
        ('BoxY', MEASUREMENTS['box_inside']['width']),
        ('BoxH', MEASUREMENTS['box_inside']['height']),
        ('Span', 288), ('Wall', 2), ('Base', 2), ('Gap', 0.8),
        ('CarW', MEASUREMENTS['race_car']['width']), ('CarL', MEASUREMENTS['race_car']['length']), ('CarH', MEASUREMENTS['race_car']['height']),
        ('GearD', MEASUREMENTS['gear_pawn']['base_diameter']), ('GearH', MEASUREMENTS['gear_pawn']['height']), ('DeckBottom', 9), ('DeckT', 2), ('GearRecess', 0.8),
        ('DrawerClear', 0.4), ('DrawerBase', 1.2), ('SeatClear', 1), ('GearClear', 0.5),
        ('SleeveW', MEASUREMENTS['sleeved_card']['width']),
        ('SleeveL', MEASUREMENTS['sleeved_card']['height']),
        ('EdgeClear', 1), ('LowerH', 13), ('LidT', 1.6),
        ('LipD', 0.8), ('LipClear', 0.3), ('LipWall', 1.2),
        ('StackReserve', 60), ('Headroom', 2),
        ('SampleStack', MEASUREMENTS['sleeved_card_stack_measurement']['design_basis_stack_height']),
        ('SampleCards', MEASUREMENTS['sleeved_card_stack_measurement']['card_count']),
        ('TotalH', '=BoxH - StackReserve - Headroom'),
        ('PlayerW', '=SleeveW + 2 * EdgeClear + 2 * Wall'),
        ('PlayerL', '=SleeveL + 2 * EdgeClear + 2 * Wall'),
        ('ModuleW', '=PlayerW'), ('ModuleH', '=TotalH / 2'),
        ('ModuleBodyH', '=ModuleH - LidT'), ('TokenW', '=Span - 3 * (PlayerW + Gap)'),
        ('PlayerRegionL', '=2 * PlayerL + Gap'),
        ('CommonL', '=Span - 2 * (PlayerL + Gap)'),
        ('RailW', '=Span - 2 * (ModuleW + Gap) - (PlayerW + Gap)'),
        ('BodyH', '=TotalH - LidT'),
        ('UpperH', '=BodyH - LowerH'),
        ('CardPitch', '=SampleStack / SampleCards'),
        ('DeckTop', '=DeckBottom + DeckT'), ('GearFloor', '=DeckTop - GearRecess'),
        ('GearWellD', '=GearD + 2 * GearClear'),
        ('CarWellW', '=CarW + 2 * SeatClear'), ('CarWellL', '=CarL + 2 * SeatClear'),
        ('BayW', '=(TokenW - 3 * Wall) / 2'), ('BayL', '=(PlayerRegionL - 5 * Wall) / 4'),
        ('DrawerH', '=DeckBottom - Base - 2 * DrawerClear'),
    ]
    cells = {}
    for row, (alias, value) in enumerate(rows, 2):
        cell = 'B' + str(row)
        cells[alias] = cell
        sheet.set('A' + str(row), alias)
        sheet.set(cell, str(value) if isinstance(value, str) or alias == 'SampleCards' else str(value) + ' mm')
        sheet.setAlias(cell, alias)
    sheet.setColumnWidth('A', 230)
    sheet.setColumnWidth('B', 250)
    sheet.set('D2', '4 maps + all mats/rules reserved above trays')
    sheet.set('D3', 'Base common mats INCLUDED in measured 4 mm')
    sheet.set('D4', 'Car11x23x7; gear base D15/H25 measured; other tokens unmeasured')
    sheet.set('D5', 'Simple locating lids; retention not validated')
    sheet.setColumnWidth('D', 450)
    doc.recompute()
    p = {alias: float(App.Units.Quantity(sheet.get(cell)).Value) for alias, cell in cells.items()}
    if min(p['RailW'] - 2 * p['Wall'], p['CommonL'] - 2 * p['Wall'], p['UpperH'] - p['Base'] - p['LipD']) <= 0:
        raise ValueError('Parameters leave no usable organizer space')
    construction = doc.addObject('App::DocumentObjectGroup', 'Construction')
    construction.Label = 'Construction - hidden'
    final_group = doc.addObject('App::DocumentObjectGroup', 'OrganizerParts')
    final_group.Label = 'Organizer parts - 31 pieces / Instructions C redesign v0.4'
    reference_group = doc.addObject('App::DocumentObjectGroup', 'References')
    reference_group.Label = 'Box / upper stack / sample cards - not printable'
    component_group = doc.addObject('App::DocumentObjectGroup', 'ComponentSamples')
    component_group.Label = 'Measured car / nominal gear envelopes - not printable'
    parts, lids, colors, layout = [], [], {}, []

    def expr(obj, prop, value):
        obj.setExpression(prop, str(value))

    def box(name, width, length, height, x, y, z):
        obj = doc.addObject('Part::Box', name)
        for prop, value in [('Length', width), ('Width', length), ('Height', height),
                            ('Placement.Base.x', x), ('Placement.Base.y', y), ('Placement.Base.z', z)]:
            expr(obj, prop, value)
        construction.addObject(obj)
        return obj

    def feature(name, typ, base, tool):
        obj = doc.addObject(typ, name)
        obj.Base, obj.Tool = base, tool
        obj.Refine = True
        construction.addObject(obj)
        return obj

    def finish(obj, label, color, role, lid=False):
        construction.removeObject(obj)
        final_group.addObject(obj)
        obj.Label = label
        obj.addProperty('App::PropertyString', 'DraftRole', 'Draft').DraftRole = role
        obj.addProperty('App::PropertyString', 'FitStatus', 'Draft').FitStatus = 'Provisional; no physical fit test'
        parts.append(obj)
        colors[obj.Name] = color
        if lid:
            lids.append(obj)
        return obj

    def tray(name, width, length, height, x, y, z, slots, notch, label, color, role):
        outer = box(name + 'Outer', width, length, height, x, y, z)
        cavity_length = '((' + length + ') - ' + str(slots + 1) + ' * Parameters.Wall) / ' + str(slots)
        cavities = []
        for index in range(slots):
            cavity = box(name + 'Pocket' + str(index + 1), '(' + width + ') - 2 * Parameters.Wall',
                         cavity_length, height, '(' + x + ') + Parameters.Wall',
                         '(' + y + ') + Parameters.Wall + ' + str(index) + ' * ((' + cavity_length + ') + Parameters.Wall)',
                         '(' + z + ') + Parameters.Base')
            cavities.append(cavity)
        if slots == 1:
            tool = cavities[0]
        else:
            tool = doc.addObject('Part::MultiFuse', name + 'PocketTool')
            tool.Shapes, tool.Refine = cavities, True
            construction.addObject(tool)
        hollow = feature(name + 'Hollow', 'Part::Cut', outer, tool)
        cutter = doc.addObject('Part::Cylinder', name + 'FingerCut')
        cutter.Placement.Rotation = App.Rotation(App.Vector(0, 0, 1), App.Vector(0, 1, 0))
        cutter.Radius = notch
        expr(cutter, 'Height', 'Parameters.Wall + 2 mm')
        expr(cutter, 'Placement.Base.x', '(' + x + ') + (' + width + ') / 2')
        expr(cutter, 'Placement.Base.y', '(' + y + ') - 1 mm')
        expr(cutter, 'Placement.Base.z', '(' + z + ') + (' + height + ')')
        construction.addObject(cutter)
        final = feature(name, 'Part::Cut', hollow, cutter)
        return finish(final, label, color, role)

    def lid(name, width, length, x, y, label, color, slots=1, z='Parameters.BodyH', split_x=None, split_y=None):
        plate = box(name + 'Plate', width, length, 'Parameters.LidT', x, y, z)
        lip_w = '(' + width + ') - 2 * (Parameters.Wall + Parameters.LipClear)'
        lip_l = '(' + length + ') - 2 * (Parameters.Wall + Parameters.LipClear)'
        lip_x = '(' + x + ') + Parameters.Wall + Parameters.LipClear'
        lip_y = '(' + y + ') + Parameters.Wall + Parameters.LipClear'
        lip_z = '(' + z + ') - Parameters.LipD'
        outer = box(name + 'LipOuter', lip_w, lip_l, 'Parameters.LipD + 0.05 mm', lip_x, lip_y, lip_z)
        inner = box(name + 'LipInner', '(' + lip_w + ') - 2 * Parameters.LipWall',
                    '(' + lip_l + ') - 2 * Parameters.LipWall', 'Parameters.LipD + 0.1 mm',
                    '(' + lip_x + ') + Parameters.LipWall', '(' + lip_y + ') + Parameters.LipWall', lip_z)
        ring = feature(name + 'Ring', 'Part::Cut', outer, inner)
        # Interrupt the skirt at token tray partitions; otherwise it hits them.
        cavity_length = '((' + length + ') - ' + str(slots + 1) + ' * Parameters.Wall) / ' + str(slots)
        for index in range(slots - 1):
            divider_y = '(' + y + ') + Parameters.Wall + ' + str(index + 1) + ' * (' + cavity_length + ') + ' + str(index) + ' * Parameters.Wall - Parameters.LipClear'
            clearance = box(name + 'DividerGap' + str(index + 1), width, 'Parameters.Wall + 2 * Parameters.LipClear',
                            'Parameters.LipD + 0.1 mm', x, divider_y, lip_z)
            ring = feature(name + 'SkirtClearance' + str(index + 1), 'Part::Cut', ring, clearance)
        if split_x is not None:
            gap = box(name + 'VerticalGap', 'Parameters.Wall + Parameters.Gap + 2 * Parameters.LipClear', length,
                      'Parameters.LipD + 0.1 mm', '('+x+') + ('+split_x+') - Parameters.LipClear', y, lip_z)
            ring = feature(name + 'ClearVertical', 'Part::Cut', ring, gap)
        if split_y is not None:
            gap = box(name + 'HorizontalGap', width, 'Parameters.Wall + 2 * Parameters.LipClear',
                      'Parameters.LipD + 0.1 mm', x, '('+y+') + ('+split_y+') - Parameters.LipClear', lip_z)
            ring = feature(name + 'ClearHorizontal', 'Part::Cut', ring, gap)
        obj = feature(name, 'Part::Fuse', plate, ring)
        return finish(obj, label, color, 'lid', True)

    player_colors = [(0.78,0.22,0.18),(0.16,0.43,0.70),(0.91,0.66,0.15),(0.18,0.58,0.43),
                     (0.30,0.33,0.37),(0.72,0.70,0.65),(0.90,0.40,0.16),(0.52,0.32,0.65)]

    def pocket_tray(name, width, length, height, x, y, z, pockets, label, color, role):
        outer = box(name+'Outer',width,length,height,x,y,z)
        cuts=[]
        for i,(cw,cl,dx,dy) in enumerate(pockets):
            cuts.append(box(name+'Pocket'+str(i),cw,cl,height,'('+x+') + ('+dx+')',
                            '('+y+') + ('+dy+')','('+z+') + Parameters.Base'))
        tool=doc.addObject('Part::MultiFuse',name+'PocketTool')
        tool.Shapes,tool.Refine=cuts,True
        construction.addObject(tool)
        hollow=feature(name+'Hollow','Part::Cut',outer,tool)
        cutter=doc.addObject('Part::Cylinder',name+'FingerCut')
        cutter.Placement.Rotation=App.Rotation(App.Vector(0,0,1),App.Vector(0,1,0))
        cutter.Radius=8
        expr(cutter,'Height','Parameters.Wall + 2 mm')
        expr(cutter,'Placement.Base.x','('+x+') + Parameters.PlayerW / 2')
        expr(cutter,'Placement.Base.y','('+y+') - 1 mm')
        expr(cutter,'Placement.Base.z','('+z+') + ('+height+')')
        construction.addObject(cutter)
        final=feature(name,'Part::Cut',hollow,cutter)
        return finish(final,label,color,role)

    # Four footprint positions, two independently removable ready sets per position.
    for row in range(2):
        for col in range(2):
            for level in range(2):
                index=(row*2+col)*2+level+1
                name='P%02d'%index
                x='1 mm + %d * (Parameters.ModuleW + Parameters.Gap)'%col
                y='1 mm + %d * (Parameters.PlayerL + Parameters.Gap)'%row
                z='%d * Parameters.ModuleH'%level
                color=player_colors[index-1]
                body=tray(name+'Body','Parameters.ModuleW','Parameters.PlayerL','Parameters.ModuleBodyH',x,y,z,1,8,
                          name+' - 24 player cards / separate car-gear carrier',color,'player_cards')
                body.addProperty('App::PropertyInteger','CardCount','Contents').CardCount=24
                body.addProperty('App::PropertyString','PocketSizes','Contents').PocketSizes='Card60x91 mm; usable14.6 under lid lip'
                lid(name+'Lid','Parameters.ModuleW','Parameters.PlayerL',x,y,name+' - locating lid',color,
                    z='('+z+') + Parameters.ModuleBodyH')
                layout.append({'name':name,'x':1+col*(p['ModuleW']+p['Gap']),'y':1+row*(p['PlayerL']+p['Gap']),
                               'z':level*p['ModuleH'],'width':p['ModuleW'],'length':p['PlayerL'],'height':p['ModuleH'],
                               'role':'player_cards','level':level,'color':list(color),'cards':24})
    side_x='1 mm + 2 * (Parameters.ModuleW + Parameters.Gap)'
    common_y='1 mm + 2 * (Parameters.PlayerL + Parameters.Gap)'
    common_specs=[
        ('Reserve',side_x,'1 mm','Parameters.PlayerW','Parameters.PlayerL','Reserve / stress24 + heat24 =48','reserve_cards',48),
        ('Sponsor',side_x,'1 mm + Parameters.PlayerL + Parameters.Gap','Parameters.PlayerW','Parameters.PlayerL','Sponsorship / base35 + 7 + 7 =49','sponsor_cards',49),
        ('Other','1 mm + 2 * (Parameters.PlayerW + Parameters.Gap)',common_y,'Parameters.PlayerW','Parameters.CommonL','Legends10 + event18 + track8 =36; one set','other_cards',36)]
    for name,x,y,w,l,label,role,count in common_specs:
        color=(0.24,0.52,0.64)
        body=tray(name+'Body',w,l,'Parameters.BodyH',x,y,'0 mm',1,10,label,color,role)
        body.addProperty('App::PropertyInteger','CardCount','Contents').CardCount=count
        lid(name+'Lid',w,l,x,y,name+' - locating lid',color)
        # Evaluated coordinates from the completed native shape are recorded later.
        layout.append({'name':name,'width':p['PlayerW'],'length':p['PlayerL'] if name!='Other' else p['CommonL'],
                       'height':p['TotalH'],'role':role,'color':list(color),'cards':count,'allocation':label})
    gx='1 mm'
    gy=common_y
    gw='2 * Parameters.PlayerW + Parameters.Gap'
    garage=pocket_tray('GarageBody',gw,'Parameters.CommonL','Parameters.BodyH',gx,gy,'0 mm',
                     [('(2 * Parameters.PlayerW + Parameters.Gap - 3 * Parameters.Wall) / 2','Parameters.CommonL - 2 * Parameters.Wall','Parameters.Wall','Parameters.Wall'),
                      ('(2 * Parameters.PlayerW + Parameters.Gap - 3 * Parameters.Wall) / 2','Parameters.CommonL - 2 * Parameters.Wall','(2 * Parameters.PlayerW + Parameters.Gap + Parameters.Wall) / 2','Parameters.Wall')],
                     'Garage /120 cards; one carrier, 60 cards per bay',(0.18,0.43,0.56),'garage_cards')
    garage.addProperty('App::PropertyInteger','CardCount','Contents').CardCount=120
    lid('GarageLid',gw,'Parameters.CommonL',gx,gy,'Garage - one lid',(0.18,0.43,0.56),
        split_x='(2 * Parameters.PlayerW + Parameters.Gap - Parameters.Wall) / 2')
    layout.append({'name':'Garage','width':2*p['PlayerW']+p['Gap'],'length':p['CommonL'],'height':p['TotalH'],
                   'role':'garage_cards','color':[0.18,0.43,0.56],'cards':120})
    tx='1 mm + 3 * (Parameters.PlayerW + Parameters.Gap)'
    tc=(0.72,0.50,0.22)
    tray('WeatherLower','Parameters.TokenW','Parameters.CommonL','Parameters.LowerH',tx,common_y,'0 mm',2,6,
         'Weather6 / road conditions12 - low serving tray; fit provisional',tc,'weather_road')
    tray('PressUpper','Parameters.TokenW','Parameters.CommonL','Parameters.UpperH',tx,common_y,'Parameters.LowerH',1,6,
         'Press corner standees2 - removable upper tray; fit provisional',tc,'press_standees')
    lid('TokensLid','Parameters.TokenW','Parameters.CommonL',tx,common_y,'Tokens - locating lid',tc)
    layout.append({'name':'Tokens','width':p['TokenW'],'length':p['CommonL'],'height':p['TotalH'],'role':'weather_press','color':list(tc)})
    # Instructions C principle: paired car/gear seats in two columns + lower pull-out tray.
    cx=tx
    cy='1 mm'
    cw='Parameters.TokenW'
    cl='Parameters.PlayerRegionL'
    outer=box('CarGearOuter',cw,cl,'Parameters.BodyH',cx,cy,'0 mm')
    upper=box('CarGearUpperCavity','Parameters.TokenW - 2 * Parameters.Wall',
              'Parameters.PlayerRegionL - 2 * Parameters.Wall','Parameters.BodyH',
              '('+cx+') + Parameters.Wall','('+cy+') + Parameters.Wall','Parameters.DeckTop')
    lower=box('CarGearDrawerCavity','Parameters.TokenW - 2 * Parameters.Wall',
              'Parameters.PlayerRegionL - Parameters.Wall','Parameters.DeckBottom - Parameters.Base',
              '('+cx+') + Parameters.Wall',cy,'Parameters.Base')
    shell=feature('CarGearShell','Part::Cut',feature('CarGearHollow','Part::Cut',outer,upper),lower)
    bosses=[]
    gear_centres=[]
    car_origins=[]
    def cylinder(name,radius,height,x,y,z):
        obj=doc.addObject('Part::Cylinder',name)
        for prop,value in [('Radius',radius),('Height',height),('Placement.Base.x',x),('Placement.Base.y',y),('Placement.Base.z',z)]:
            expr(obj,prop,value)
        construction.addObject(obj)
        return obj
    for col in range(2):
        for row in range(4):
            idx=col*4+row+1
            seat='Seat%02d'%idx
            ox='('+cx+') + %d * (Parameters.BayW + Parameters.Wall)'%col
            mid_y='('+cy+') + Parameters.Wall + Parameters.BayL / 2 + %d * (Parameters.BayL + Parameters.Wall)'%row
            car_x=('('+cx+') + Parameters.BayW - Parameters.CarWellW - 2 mm' if col==0
                   else '('+cx+') + Parameters.TokenW - Parameters.BayW + 2 mm')
            car_y='('+mid_y+') - Parameters.CarWellL / 2'
            gear_offset='2 * Parameters.Wall + 1 mm + Parameters.GearWellD / 2'
            gear_x=('('+cx+') + ('+gear_offset+')' if col==0 else '('+cx+') + Parameters.TokenW - ('+gear_offset+')')
            well=cylinder(seat+'GearWell','Parameters.GearWellD / 2','Parameters.GearRecess + 0.1 mm',gear_x,mid_y,'Parameters.GearFloor')
            shell=feature(seat+'Recess','Part::Cut',shell,well)
            cup_outer=cylinder(seat+'GearCupOuter','Parameters.GearWellD / 2 + Parameters.Wall','4 mm',gear_x,mid_y,'Parameters.DeckTop')
            cup_inner=cylinder(seat+'GearCupInner','Parameters.GearWellD / 2','4.1 mm',gear_x,mid_y,'Parameters.DeckTop')
            bosses.append(feature(seat+'GearCup','Part::Cut',cup_outer,cup_inner))
            car_outer=box(seat+'CarCradleOuter','Parameters.CarWellW + 2 * Parameters.Wall','Parameters.CarWellL + 2 * Parameters.Wall','6 mm',
                          '('+car_x+') - Parameters.Wall','('+car_y+') - Parameters.Wall','Parameters.DeckTop')
            car_inner=box(seat+'CarCradleInner','Parameters.CarWellW','Parameters.CarWellL','6.1 mm',car_x,car_y,'Parameters.DeckTop')
            cradle=feature(seat+'CarCradleHollow','Part::Cut',car_outer,car_inner)
            finger=doc.addObject('Part::Cylinder',seat+'CarFingerCut')
            finger.Placement.Rotation=App.Rotation(App.Vector(0,0,1),App.Vector(1,0,0))
            finger.Radius=4
            expr(finger,'Height','Parameters.CarWellW + 2 * Parameters.Wall + 2 mm')
            expr(finger,'Placement.Base.x','('+car_x+') - Parameters.Wall - 1 mm')
            expr(finger,'Placement.Base.y',mid_y)
            expr(finger,'Placement.Base.z','Parameters.DeckTop + 6 mm')
            construction.addObject(finger)
            bosses.append(feature(seat+'CarCradle','Part::Cut',cradle,finger))
            gear_centres.append((idx,gear_x,mid_y))
            car_origins.append((idx,car_x,car_y))
    bosses.append(box('CarGearCentralSpine','Parameters.Wall','Parameters.PlayerRegionL - 2 * Parameters.Wall','8 mm',
                      '('+cx+') + Parameters.Wall + Parameters.BayW','('+cy+') + Parameters.Wall','Parameters.DeckTop'))
    for row in range(1,4):
        bosses.append(box('CarGearSeatDivider'+str(row),'Parameters.TokenW - 2 * Parameters.Wall','Parameters.Wall','4 mm',
                          '('+cx+') + Parameters.Wall','('+cy+') + Parameters.Wall + %d * Parameters.BayL + %d * Parameters.Wall'%(row,row-1),'Parameters.DeckTop'))
    # Side reliefs expose the vehicles; the full-height corner posts support the lid.
    for side in range(2):
        cut=box('CarGearSideRelief'+str(side),'Parameters.Wall + 0.2 mm','Parameters.PlayerRegionL - 16 mm','Parameters.BodyH',
                '('+cx+') + %d * (Parameters.TokenW - Parameters.Wall) - 0.1 mm'%side,
                '('+cy+') + 8 mm','Parameters.DeckTop + 7 mm')
        shell=feature('CarGearSideCut'+str(side),'Part::Cut',shell,cut)
    base_notch=cylinder('CarGearBaseFingerCut','10 mm','Parameters.Base + 0.1 mm',
                        '('+cx+') + Parameters.TokenW / 2','('+cy+') - 2 mm','0 mm')
    shell=feature('CarGearBaseRelief','Part::Cut',shell,base_notch)
    complete=doc.addObject('Part::MultiFuse','CarGearComplete')
    complete.Shapes,complete.Refine=[shell]+bosses,True
    construction.addObject(complete)
    upper_plane=box('CarGearUpperPrintPlane',cw,cl,'Parameters.BodyH',cx,cy,'Parameters.DeckBottom')
    lower_plane=box('CarGearLowerPrintPlane',cw,cl,'Parameters.DeckBottom',cx,cy,'0 mm')
    body=feature('CarGearUpperSplit','Part::Common',complete,upper_plane)
    frame_base=feature('CarGearLowerSplit','Part::Common',complete,lower_plane)
    keys=[]
    for side in range(2):
        for end in range(2):
            key_index=side*2+end
            kx='('+cx+') + %d * (Parameters.TokenW - Parameters.Wall)'%side
            ky='('+cy+') + '+('8 mm' if end==0 else 'Parameters.PlayerRegionL - 12 mm')
            keys.append(box('CarGearLocator'+str(key_index),'Parameters.Wall','4 mm','1.5 mm',kx,ky,'Parameters.DeckBottom'))
            gap=box('CarGearLocatorGap'+str(key_index),'Parameters.Wall + 0.4 mm','4.4 mm','1.7 mm',
                    '('+kx+') - 0.2 mm','('+ky+') - 0.2 mm','Parameters.DeckBottom')
            body=feature('CarGearBody' if key_index==3 else 'CarGearLocatorFit'+str(key_index),'Part::Cut',body,gap)
    frame=doc.addObject('Part::MultiFuse','CarGearFrame')
    frame.Shapes,frame.Refine=[frame_base]+keys,True
    construction.addObject(frame)
    finish(frame,'C - lower frame / 4 locating keys; assembly retention unverified',(0.31,0.38,0.44),'car_gear_lower_frame')
    finish(body,'C - upper car/gear deck / 8 colours; print separately',(0.31,0.38,0.44),'car_gear_carrier')
    body.addProperty('App::PropertyString','ContentsSummary','Contents').ContentsSummary='8 cars11x23x7; 8 upright gears baseD15/H25; gear socketD16'
    body.addProperty('App::PropertyString','GearFitAssumption','Contents').GearFitAssumption='15mm is measured base diameter; upper part assumed within same cylinder envelope'
    # Lid has skirt interruptions over the central spine and the three seat partitions.
    lid('CarGearLid',cw,cl,cx,cy,'C - carrier locating lid',(0.31,0.38,0.44),slots=4,
        split_x='Parameters.Wall + Parameters.BayW')
    dw='Parameters.TokenW - 2 * Parameters.Wall - 2 * Parameters.DrawerClear'
    dl='Parameters.PlayerRegionL - Parameters.Wall - 2 * Parameters.DrawerClear'
    dx='('+cx+') + Parameters.Wall + Parameters.DrawerClear'
    dy='('+cy+') + Parameters.DrawerClear'
    dz='Parameters.Base + Parameters.DrawerClear'
    drawer_outer=box('CarGearDrawerOuter',dw,dl,'Parameters.DrawerH',dx,dy,dz)
    drawer_inner=box('CarGearDrawerInner','('+dw+') - 2 * Parameters.DrawerBase','('+dl+') - 2 * Parameters.DrawerBase','Parameters.DrawerH',
                     '('+dx+') + Parameters.DrawerBase','('+dy+') + Parameters.DrawerBase','('+dz+') + Parameters.DrawerBase')
    drawer=feature('CarGearDrawerHollow','Part::Cut',drawer_outer,drawer_inner)
    notch=doc.addObject('Part::Cylinder','CarGearDrawerFingerCut')
    notch.Placement.Rotation=App.Rotation(App.Vector(0,0,1),App.Vector(0,1,0))
    notch.Radius=8
    expr(notch,'Height','Parameters.DrawerBase + 2 mm')
    expr(notch,'Placement.Base.x','('+cx+') + Parameters.TokenW / 2')
    expr(notch,'Placement.Base.y','('+dy+') - 1 mm')
    expr(notch,'Placement.Base.z','('+dz+') + Parameters.DrawerH')
    construction.addObject(notch)
    finish(feature('CarGearDrawer','Part::Cut',drawer,notch),'C - lower pull-out tray / provisional 5mm usable height',
           (0.46,0.51,0.56),'optional_lower_drawer')
    layout.append({'name':'CarGear','width':p['TokenW'],'length':p['PlayerRegionL'],'height':p['TotalH'],
                   'role':'car_gear_carrier','color':[0.31,0.38,0.44],'cars':8,'gears':8})
    refs = [box('InternalBoxEnvelope', 'Parameters.BoxX', 'Parameters.BoxY', 'Parameters.BoxH', '0 mm', '0 mm', '0 mm'),
            box('UpperFlatStackReserve', 'Parameters.Span', 'Parameters.Span', 'Parameters.StackReserve', '1 mm', '1 mm', 'Parameters.TotalH'),
            box('SleevedCardSample24', 'Parameters.SleeveW', 'Parameters.SleeveL', 'Parameters.SampleStack',
                '1 mm + Parameters.Wall + Parameters.EdgeClear', '1 mm + Parameters.Wall + Parameters.EdgeClear', 'Parameters.Base')]
    for idx,gx,gy in gear_centres:
        gear=cylinder('GearSampleP%02d'%idx,'Parameters.GearD / 2','Parameters.GearH',gx,gy,'Parameters.GearFloor')
        gear.Label='P%02d - gear nominal cylinder, baseD15 / H25; not printable'%idx
        refs.append(gear)
    for idx,px,py in car_origins:
        car=box('CarSampleP%02d'%idx,'Parameters.CarW','Parameters.CarL','Parameters.CarH',
                '('+px+') + Parameters.SeatClear','('+py+') + Parameters.SeatClear','Parameters.DeckTop')
        car.Label='P%02d - measured car envelope11x23x7; not printable'%idx
        refs.append(car)
    for ref in refs:
        construction.removeObject(ref)
        (component_group if ref.Name.startswith(('CarSample','GearSample')) else reference_group).addObject(ref)
        ref.addProperty('App::PropertyString', 'DraftRole', 'Draft').DraftRole = 'reference_not_printable'
    doc.recompute()
    if App.GuiUp:
        import FreeCADGui as Gui
        for obj in construction.Group + refs:
            obj.ViewObject.Visibility = False
        for obj in parts:
            obj.ViewObject.Visibility = obj not in lids
            obj.ViewObject.ShapeColor = colors[obj.Name]
            obj.ViewObject.LineColor = (0.15, 0.17, 0.20)
        Gui.activeDocument().activeView().viewAxonometric()
        Gui.activeDocument().activeView().fitAll()
    for module in layout:
        obj=doc.getObject(module['name']+'Body') or doc.getObject(module['name']+'Lower') or doc.getObject(module['name'])
        if obj is None and module['name']=='Tokens': obj=doc.WeatherLower
        bounds=obj.Shape.BoundBox
        module['x'],module['y'],module['z']=bounds.XMin,bounds.YMin,0 if module['name']=='CarGear' else bounds.ZMin
    return doc, parts, lids, refs, p, cells, layout, colors


def export_draft(doc, parts, lids, refs, p, cells, layout, colors):
    stamp = datetime.now(timezone(timedelta(hours=9))).strftime('%Y%m%d_%H%M%S_%f')
    output = PROJECT_ROOT / 'output' / ('heat_draft_' + stamp)
    output.mkdir(parents=True, exist_ok=False)
    (output / 'stl').mkdir()
    doc.recompute()
    doc.saveAs(str(output / 'HeatOrganizerDraft.FCStd'))
    Part.export(parts, str(output / 'HeatOrganizerDraft-assembled.step'))
    unique = [('P01Body',8),('P01Lid',8),('ReserveBody',1),('ReserveLid',1),('SponsorBody',1),('SponsorLid',1),('OtherBody',1),('OtherLid',1),('GarageBody',1),('GarageLid',1),('WeatherLower',1),('PressUpper',1),('TokensLid',1),('CarGearBody',1),('CarGearFrame',1),('CarGearLid',1),('CarGearDrawer',1)]
    stls = []
    for name, quantity in unique:
        obj = doc.getObject(name)
        shape = obj.Shape.copy()
        # Print lids with the broad top face on the bed and locating ring upward.
        if name.endswith('Lid'):
            shape.rotate(App.Vector(0, 0, 0), App.Vector(1, 0, 0), 180)
        bounds = shape.BoundBox
        shape.translate(App.Vector(-bounds.XMin, -bounds.YMin, -bounds.ZMin))
        mesh = MeshPart.meshFromShape(Shape=shape, LinearDeflection=0.08, AngularDeflection=0.3, Relative=False)
        file_name = name + '_x' + str(quantity) + '.stl'
        mesh.write(str(output / 'stl' / file_name))
        stls.append({'file': 'stl/' + file_name, 'quantity': quantity, 'name': name,
                     'volume_mm3': shape.Volume, 'outer_mm': [shape.BoundBox.XLength, shape.BoundBox.YLength, shape.BoundBox.ZLength],
                     'print_orientation': 'flat lid face down; locating ring up' if name.endswith('Lid') else 'base down'})
    preview = []
    for obj in parts:
        if obj in lids:
            continue
        vertices, triangles = obj.Shape.tessellate(0.25)
        preview.append({'name': obj.Name, 'color': list(colors[obj.Name]),
                        'vertices': [[v.x, v.y, v.z] for v in vertices], 'triangles': [list(t) for t in triangles]})
    (output / 'preview-mesh.json').write_text(json.dumps(preview), encoding='utf-8')
    component_preview=[]
    for obj in refs:
        if not obj.Name.startswith(('CarSample','GearSample')): continue
        vertices,triangles=obj.Shape.tessellate(0.2)
        index=int(obj.Name[-2:])-1
        component_preview.append({'name':obj.Name,'color':list([(0.78,0.22,0.18),(0.16,0.43,0.70),(0.91,0.66,0.15),(0.18,0.58,0.43),
                                                              (0.30,0.33,0.37),(0.72,0.70,0.65),(0.90,0.40,0.16),(0.52,0.32,0.65)][index]),
                                  'vertices':[[v.x,v.y,v.z] for v in vertices],'triangles':[list(t) for t in triangles]})
    (output/'component-reference-mesh.json').write_text(json.dumps(component_preview),encoding='utf-8')
    shared_depth = p['BodyH'] - p['LipD'] - p['Base']
    manifest = {'version':'0.4_instructions_C_redesign', 'reference_pdf':r'C:\Users\Twibap\Downloads\Instructions-Heat-All-In-Board-Game-Insert-Organizer-The-Dicetroyers-min.pdf', 'reference_videos':['https://youtu.be/xePYRwZCSzQ','https://youtube.com/shorts/PnYFqH4tk2Y'], 'status': 'draft_not_physical_fit_verified', 'units': 'mm', 'parameters': p, 'cells': cells,
                'component_allocation': json.loads((PROJECT_ROOT / 'heat-component-allocation.json').read_text(encoding='utf-8')), 'layout': layout, 'part_count': len(parts), 'stl_files': stls, 'freecad_version': list(App.Version()),
                'player_card_usable_depth': p['ModuleBodyH'] - p['Base'] - p['LipD'],
                'player_upper_clear_height_under_lip': p['ModuleBodyH'] - p['Base'] - p['LipD'],
                'shared_card_usable_depth_under_lip': shared_depth,
                'shared_cards_per_bin_estimate': math.floor((shared_depth - 1) / p['CardPitch']),
                'gear_seat':{'orientation':'upright','socket_diameter':p['GearWellD'],'socket_floor':p['GearFloor'],'remaining_shelf_floor':p['GearFloor']-p['DeckBottom'],'gear_top_clearance':p['BodyH']-p['GearFloor']-p['GearH']},
                'lower_drawer_usable_height':p['DrawerH']-p['DrawerBase'],
                'carrier_print_split_plane':p['DeckBottom'],
                'carrier_assembly_retention':'Upper deck and frame separate; 4 alignment keys with0.2mm side clearance. Lift upper car tray independently; retention unverified.',
                'maximum_print_part_xy': max(max(s['outer_mm'][:2]) for s in stls),
                'assumptions': ['Two track expansions add one player each: 8 card-only modules stacked in four pairs; cars/gears in a shared carrier.',
                                'Player set confirmed: basic12 + starting3 + stress3 + heat6 =24 cards; 8 sets.',
                                '4-map thickness 50 mm is estimated; complete flat stack must fit 60 mm reserve.',
                                'Measured car11x23x7 and gear baseD15/H25. Entire gear assumed within D15 cylinder; actual upper profile unmeasured.',
                                'Instructions C inspired two-column car/gear carrier and lower pull-out tray. Drawer usable5mm, contents physical fit unmeasured.',
                                'Scorepads require measured storage allocation; add thickness to upper stack if stored above trays.',
                                'Lids have clearance skirts only; snap fit and vertical transport retention not validated.'],
                'references_not_printable': [obj.Name for obj in refs]}
    (output / 'manifest.json').write_text(json.dumps(manifest, ensure_ascii=False, indent=2), encoding='utf-8')
    (PROJECT_ROOT / 'output' / 'latest-heat-draft.txt').write_text(str(output), encoding='utf-8')
    App.Console.PrintMessage('Heat draft exported to: ' + str(output) + '\n')
    return output


draft_document, draft_parts, draft_lids, draft_refs, draft_parameters, draft_cells, draft_layout, draft_colors = build_draft()
draft_output = export_draft(draft_document, draft_parts, draft_lids, draft_refs, draft_parameters, draft_cells, draft_layout, draft_colors)
